submodule ietf-ipv6-router-advertisements-2 {
  yang-version "1.1";

  belongs-to ietf-ipv6-unicast-routing-2 {
    prefix "v6ur";
  }

  import ietf-inet-types {
    prefix "inet";
  }

  import ietf-interfaces {
    prefix "if";
  }

  import ietf-ip {
    prefix "ip";
  }

  organization
    "IETF NETMOD (NETCONF Data Modeling Language) Working Group";
  contact
    "WG Web:   <https://datatracker.ietf.org/wg/netmod/>
     WG List:  <mailto:netmod@ietf.org>

     WG Chair: Lou Berger
               <mailto:lberger@labn.net>

     WG Chair: Kent Watsen
               <mailto:kwatsen@juniper.net>

     Editor:   Ladislav Lhotka
               <mailto:lhotka@nic.cz>

     Editor:   Acee Lindem
               <mailto:acee@cisco.com>

     Editor:   Yingzhen Qu
               <mailto:yingzhen.qu@huawei.com>";

  description
    "This YANG module augments the 'ietf-ip' module with
     configuration and state data of IPv6 router advertisements.

     Copyright (c) 2017 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (http://trustee.ietf.org/license-info).

     The key words 'MUST', 'MUST NOT', 'REQUIRED', 'SHALL', 'SHALL
     NOT', 'SHOULD', 'SHOULD NOT', 'RECOMMENDED', 'MAY', and
     'OPTIONAL' in the module text are to be interpreted as
     described in RFC 2119.

     This version of this YANG module is part of RFC 8022;
     see the RFC itself for full legal notices.";

  reference
    "RFC 4861: Neighbor Discovery for IP version 6 (IPv6).";

  revision 2017-10-05 {
    description
      "Network Managment Datastore Architecture (NDMA)
       Initial Revision
       Replaces ietf-ipv6-router-advertisements.yang";
    reference
      "RFC XXXX: A YANG Data Model for Routing Management
       (NDMA Version)";
  }

  augment "/if:interfaces/if:interface/ip:ipv6" {
    description
      "Augment interface configuration with parameters of IPv6
       router advertisements.";
    container ipv6-router-advertisements {
      description
        "Configuration of IPv6 Router Advertisements.";
      leaf send-advertisements {
        type boolean;
        default "false";
        description
          "A flag indicating whether or not the router sends
           periodic Router Advertisements and responds to
           Router Solicitations.";
        reference
          "RFC 4861: Neighbor Discovery for IP version 6 (IPv6) -
           AdvSendAdvertisements.";
      }
      leaf max-rtr-adv-interval {
        type uint16 {
          range "4..1800";
        }
        units "seconds";
        default "600";
        description
          "The maximum time allowed between sending unsolicited
           multicast Router Advertisements from the interface.";
        reference
          "RFC 4861: Neighbor Discovery for IP version 6 (IPv6) -
           MaxRtrAdvInterval.";
      }
      leaf min-rtr-adv-interval {
        type uint16 {
          range "3..1350";
        }
        units "seconds";
        must ". <= 0.75 * ../max-rtr-adv-interval" {
          description
            "The value MUST NOT be greater than 75% of
             'max-rtr-adv-interval'.";
        }
        description
          "The minimum time allowed between sending unsolicited
           multicast Router Advertisements from the interface.

           The default value to be used operationally if this leaf
           is not configured is determined as follows:

           - if max-rtr-adv-interval >= 9 seconds, the default
             value is 0.33 * max-rtr-adv-interval;

           - otherwise, it is 0.75 * max-rtr-adv-interval.";
        reference
          "RFC 4861: Neighbor Discovery for IP version 6 (IPv6) -
           MinRtrAdvInterval.";
      }
      leaf managed-flag {
        type boolean;
        default "false";
        description
          "The value to be placed in the 'Managed address
           configuration' flag field in the Router Advertisement.";
        reference
          "RFC 4861: Neighbor Discovery for IP version 6 (IPv6) -
           AdvManagedFlag.";
      }
      leaf other-config-flag {
        type boolean;
        default "false";
        description
          "The value to be placed in the 'Other configuration' flag
           field in the Router Advertisement.";
        reference
          "RFC 4861: Neighbor Discovery for IP version 6 (IPv6) -
           AdvOtherConfigFlag.";
      }
      leaf link-mtu {
        type uint32;
        default "0";
        description
          "The value to be placed in MTU options sent by the
           router. A value of zero indicates that no MTU options
           are sent.";
        reference
          "RFC 4861: Neighbor Discovery for IP version 6 (IPv6) -
           AdvLinkMTU.";
      }
      leaf reachable-time {
        type uint32 {
          range "0..3600000";
        }
        units "milliseconds";
        default "0";
        description
          "The value to be placed in the Reachable Time field in
           the Router Advertisement messages sent by the router.  A
           value of zero means unspecified (by this router).";
        reference
          "RFC 4861: Neighbor Discovery for IP version 6 (IPv6) -
           AdvReachableTime.";
      }
      leaf retrans-timer {
        type uint32;
        units "milliseconds";
        default "0";
        description
          "The value to be placed in the Retrans Timer field in the
           Router Advertisement messages sent by the router.  A
           value of zero means unspecified (by this router).";
        reference
          "RFC 4861: Neighbor Discovery for IP version 6 (IPv6) -
           AdvRetransTimer.";
      }
      leaf cur-hop-limit {
        type uint8;
        description
          "The value to be placed in the Cur Hop Limit field in the
           Router Advertisement messages sent by the router.  A
           value of zero means unspecified (by this router).

           If this parameter is not configured, the device SHOULD
           use the value specified in IANA Assigned Numbers that
           was in effect at the time of implementation.";
        reference
          "RFC 4861: Neighbor Discovery for IP version 6 (IPv6) -
           AdvCurHopLimit.

           IANA: IP Parameters,
           http://www.iana.org/assignments/ip-parameters";
      }
      leaf default-lifetime {
        type uint16 {
          range "0..9000";
        }
        units "seconds";
        description
          "The value to be placed in the Router Lifetime field of
           Router Advertisements sent from the interface, in
           seconds. It MUST be either zero or between
           max-rtr-adv-interval and 9000 seconds.  A value of zero
           indicates that the router is not to be used as a default
           router.  These limits may be overridden by specific
           documents that describe how IPv6 operates over different
           link layers.

           If this parameter is not configured, the device SHOULD
           use a value of 3 * max-rtr-adv-interval.";
        reference
          "RFC 4861: Neighbor Discovery for IP version 6 (IPv6) -
           AdvDefaultLifeTime.";
      }
      container prefix-list {
        description
          "Configuration of prefixes to be placed in Prefix
           Information options in Router Advertisement messages
           sent from the interface.

           Prefixes that are advertised by default but do not have
           their entries in the child 'prefix' list are advertised
           with the default values of all parameters.

           The link-local prefix SHOULD NOT be included in the list
           of advertised prefixes.";
        reference
          "RFC 4861: Neighbor Discovery for IP version 6 (IPv6) -
           AdvPrefixList.";
        list prefix {
          key "prefix-spec";
          description
            "Configuration of an advertised prefix entry.";
          leaf prefix-spec {
            type inet:ipv6-prefix;
            description
              "IPv6 address prefix.";
          }
          choice control-adv-prefixes {
            default "advertise";
            description
              "Either the prefix is explicitly removed from the
               set of advertised prefixes, or the parameters with
               which it is advertised are specified (default
               case).";
            leaf no-advertise {
              type empty;
              description
                "The prefix will not be advertised.

                 This can be used for removing the prefix from the
                 default set of advertised prefixes.";
            }
            case advertise {
              leaf valid-lifetime {
                type uint32;
                units "seconds";
                default "2592000";
                description
                  "The value to be placed in the Valid Lifetime in
                   the Prefix Information option.  The designated
                   value of all 1's (0xffffffff) represents
                   infinity.";
                reference
                  "RFC 4861: Neighbor Discovery for IP version 6
                   (IPv6) - AdvValidLifetime.";
              }
              leaf on-link-flag {
                type boolean;
                default "true";
                description
                  "The value to be placed in the on-link flag
                   ('L-bit') field in the Prefix Information
                   option.";
                reference
                  "RFC 4861: Neighbor Discovery for IP version 6
                   (IPv6) - AdvOnLinkFlag.";
              }
              leaf preferred-lifetime {
                type uint32;
                units "seconds";
                must ". <= ../valid-lifetime" {
                  description
                    "This value MUST NOT be greater than
                     valid-lifetime.";
                }
                default "604800";
                description
                  "The value to be placed in the Preferred Lifetime
                   in the Prefix Information option.  The
                   designated value of all 1's (0xffffffff)
                   represents infinity.";
                reference
                  "RFC 4861: Neighbor Discovery for IP version 6
                   (IPv6) - AdvPreferredLifetime.";
              }
              leaf autonomous-flag {
                type boolean;
                default "true";
                description
                  "The value to be placed in the Autonomous Flag
                   field in the Prefix Information option.";
                reference
                  "RFC 4861: Neighbor Discovery for IP version 6
                   (IPv6) - AdvAutonomousFlag.";
              }
            }
          }
        }
      }
    }
  }
}
